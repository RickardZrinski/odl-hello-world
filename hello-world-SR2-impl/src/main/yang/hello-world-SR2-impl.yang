module hello-world-SR2-impl {

    yang-version 1;
    namespace "urn:opendaylight:params:xml:ns:yang:controller:config:hello-world-SR2:impl";
    prefix "hello-world-SR2-impl";

    import config { prefix config; revision-date 2013-04-05; }
    import rpc-context { prefix rpcx; revision-date 2013-06-17; }
    import opendaylight-md-sal-binding { prefix mdsal; revision-date 2013-10-28; }

    description
        "This module contains the base YANG definitions for
        hello-world-SR2 impl implementation.";

    revision "2014-01-31" {
        description
            "Initial revision.";
    }

    // This is the definition of a service implementation
    identity hello-world-SR2-impl {
            base config:module-type;
            
            // Specifies the prefix for generated java classes.
            config:java-name-prefix HelloWorld;
    }

    augment "/config:modules/config:module/config:configuration" {
        case hello-world-SR2-impl {
            when "/config:modules/config:module/config:type = 'hello-world-SR2-impl'";

                container rpc-registry {
                    uses config:service-ref {
                        refine type {
                            mandatory true;
                            config:required-identity mdsal:binding-rpc-registry;
                        }
                    }
                }

                container data-broker {
                    uses config:service-ref {
                    refine type {
                        mandatory false;
                        config:required-identity mdsal:binding-async-data-broker;
                    }
                }
            }
        }
    }
}
